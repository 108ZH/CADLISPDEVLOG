(defun c:demo()
	(GC)
	(alert "我的第一个CAD二次开发程序")
	(setq c1 (getpoint "\n输入一个基点"))
	(setq height (getreal "\n输入一个长值"))
	(setq width (getreal "\n输入一个宽值"))
	(setq c2 (polar c1 0 width ))
	(setq c3 (polar c2 (/ pi 2) height))
	(setq c4 (polar c1 (/ pi 2) height))
	(command "PLINE" c1 c2 c3 c4 "c" "")
	;;;;;;;;;画十线
	(setq a1 (polar c1 (/ pi 2) (/ height 2) ))
	(setq a2 (polar c1 0 (/ width 2) ))
	(setq a3 (polar c2 (/ pi 2) (/ height 2) ))
	(setq a4 (polar c3 pi (/ width 2) ))
	(command "line" a1 a3 "")
	(command "line" a2 a4 "")
	(princ)
)
